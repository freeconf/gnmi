module car {
	description "Car goes beep beep";

	revision 2023-03-27;
	namespace "freeconf.org";
	prefix "car";

	leaf speed {
		description "How fast the car goes";
	    type int32;
		units milesPerSecond;
	}

	leaf miles {
		description "How many miles has car moved";
		config false;
	    type decimal64 {
			fraction-digits 2;
		}
	}

	rpc reset {
		description "Reset the odometer";
	}

    notification update {
        description "important state information about your car";
    }
}
